# Transmission_Requirements

## #1: Gear Selection Safety [EX.] (Functional)
| The transmission controller shall permit gear selection only when operating conditions are valid for the requested gear. |
| --- |

### #2: Park Engagement [EX.] (Functional)
| The transmission controller shall permit engagement of PARK only when \|vehSpd\| < 0.1 m/s |
| --- |

### #14: Reverse to Drive (Functional)
The transmission controller shall permit engagement of drive only when |vehSpd| > -0.5 m/s

### #15: Drive to Reverse (Functional)
The transmission controller shall permit engagement of reverse only when |vehSpd| < 0.5 m/s

### #16: Neutral Gear (Functional)
The transmission controller shall permit engagement of neutral gear operation regardless of vehicle speed.

## #3: Engine Operating Limits [EX.] (Functional)
| The transmission controller shall prevent operation of the engine outside its allowable operating range. |
| --- |

### #4: Maximum Engine Speed [EX.] (Functional)
| The transmission controller shall prevent engine speed from exceeding 7250 RPM. COMPLETED. |
| --- |
- Rationale: Higher engine speeds will cause the internal piston forces to excess material limitations.

### #12: Minimum Engine Speed (Functional)
| The transmission controller shall prevent engine speed from dipping below 800 RPM. |
| --- |

## #9: Driver Request Handling [EX.] (Functional)
| The transmission controller shall process driver gear requests according to transmission operating constraints. |
| --- |

### #10: Park Request Protection [EX.] (Functional)
The transmission controller shall always command neutral when park is selected
- Rationale: If the transmission is in any drive or reverse gears it will cause undue strain on the engine and torque converter.

## #11: Vehicle Performance [EX.] (Functional)
The vehicle shall accelerate from 0 to 60 mph in less than 12 seconds when wide-open-throttle is applied (100% throttle)
- Rationale: If 0-60 acceleration time is greater than 12 seconds it will create unsafe situations on the road during merging and other high-acceleration manoeuvers.

## #17: Peak Efficiency Operation (Functional)
The transmission controller shall select the highest gear that allows the engine to remain operating withing 1500–2500 RPM (the most efficient operating point for vehicles)

## #18: Transmission Modification Time (Functional)
The transmission shall not exceed 1 second to complete a gear shift.

## #19: Parking Brake (Functional)
The parking actuator must be opened and closed within the specified time when park or something other than park is selected.

### #20: Parking Brake Close Time (Functional)
When park is initiated, the parking actuator will close within 100 ms.

### #21: Parking Brake Open Time (Functional)
When park is left, the parking actuator will open within 100 ms.
